RDN-MIB DEFINITIONS ::= BEGIN

        IMPORTS
            MODULE-IDENTITY, enterprises
                FROM SNMPv2-SMI;


		-- RiverDelta enterprise module definition

        riverdelta MODULE-IDENTITY
            LAST-UPDATED "0005230000Z" -- example "9501201225Z"
									   -- Fri Jan 20 12:25:50 PST 1995
            ORGANIZATION "Motorola"
            CONTACT-INFO "Motorola
                          3 Highwood Drive
                          Tewksbury, MA 01867
                          Tel: +1 978 858 2000
                          Fax: +1 978 858 2399
                          E-mail:  BSRSNMP@maillist2001.mot.com

                          Tom Keske 
                          Motorola BCS
                          20 Cabot Blvd. MA07 M2-330
                          Mansfield, MA 02048
                          Tel: 1-508-851-8325
                          Fax: 1-508-851-8510
                          E-mail: Tom.Keske@motorola.com"
            DESCRIPTION
                    "MIB module definition for Motorola."
            REVISION     "0004040000Z"
            DESCRIPTION
                    "Initial creation."
            REVISION     "0005230000Z"
            DESCRIPTION
                    "Moved 'riverdelta' definition into a separate
					file; this allows an external module to
					not include the entire riverdelta chassis mib
					when needing only the 'riverdelta' definition."
            ::= { enterprises 4981 }

    END
